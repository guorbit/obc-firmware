GUI-SUBTYPE DEFINITIONS ::=
BEGIN

IMPORTS Location-Fix-Packet FROM OBC-MODEL-DATAVIEW




Mode-Change-Packet FROM OBC-MODEL-DATAVIEW


 ;




Gui-send-tm-aoi-lfp ::= Location-Fix-Packet




Gui-send-tm-mcp-mcp ::= Mode-Change-Packet







END
