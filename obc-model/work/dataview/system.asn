-- Dataview generated on-the-fly providing information on the system
-- and made available to the user code.
System-Dataview DEFINITIONS ::=
BEGIN

-- List of functions (instances) present in the system
PID ::= ENUMERATED {
    hal,
    gui,
    loc-provider,
    state-handler-entrypoint,
    tc-provider,
    tm-collection,
    
    env
}

END
