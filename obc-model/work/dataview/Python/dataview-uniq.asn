OBC-MODEL-DATAVIEW DEFINITIONS ::=
BEGIN

-- ASN.1 Type definitions must start with an uppercase
-- Field names in records (SEQUENCE) must start with a lowercase
-- Underscores are not allowed: use dash (hyphen) 
-- For integers do not assume that small ranges will be translated to small
-- types in C or Ada (expect unsigned or signed 64 bits types with subtypes
-- for the range in Ada)

-- Simple types:

-- TASTE-Boolean ::= BOOLEAN
-- MyInteger   ::= INTEGER (0..255)
-- MyReal      ::= REAL (0.0 .. 1000.0)
-- MyBool      ::= BOOLEAN
-- MyEnum      ::= ENUMERATED { hello, world, how-are-you }

-- Complex types:

--  MySeq       ::= SEQUENCE {
--      input-data  MyInteger,
--      output-data MyInteger,
--      validity    ENUMERATED { valid, invalid }
--  }
--
--  MyChoice    ::= CHOICE {
--      a BOOLEAN,
--      b MySeq
--  }
--
--  MySeqOf     ::= SEQUENCE (SIZE (2)) OF MyEnum
--
--  MyOctStr    ::= OCTET STRING (SIZE (3))
--
--  -- You can also declare constants
--  myVar       MySeqOf     ::= { hello, world }

CounterK                ::= INTEGER (0 .. 1000)

Time-UNIX               ::= INTEGER (0 .. 4294967294)   -- overflow in 2106

Latitude-WGS84          ::= REAL (-90.0 .. 90.0)
Longitude-WGS84         ::= REAL (-180.0 .. 180.0)
Location                ::= SEQUENCE {
    lat             Latitude-WGS84,
    lon             Longitude-WGS84
}

Temperature-Generic     ::= REAL (-200.0 .. 200.0)
Deployment-Digital      ::= BOOLEAN
Deployment-Analogue     ::= REAL (0.0 .. 100.0)

System-Mode             ::= INTEGER (0 .. 4)
-- ENUMERATED {
--    idle,
--    uplink,
--    downlink,
--    imaging,
--    processing
-- }

Subsystem-Address       ::= INTEGER (0 .. 6)
-- ENUMERATED {
--    obc,
--    comms,
--    electrical,
--    mechanical,
--    control,
--    software,
--    payload
-- }

Mode-Change-Packet      ::= SEQUENCE {
    target-addr     Subsystem-Address,
    target-mode     System-Mode,
    ttl-ms          INTEGER (0 .. 10000)
}

Location-Fix-Packet     ::= SEQUENCE {
    t               Time-UNIX,
    lat             Latitude-WGS84,
    lon             Longitude-WGS84
}

END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END


-- Dataview generated on-the-fly providing information on the system
-- and made available to the user code.
System-Dataview DEFINITIONS ::=
BEGIN

-- List of functions (instances) present in the system
PID ::= ENUMERATED {
    gui,
    loc-provider,
    state-handler-entrypoint,
    tc-provider,
    tc-validation,
    tm-collection,
    tm-provider,
    
    env
}

END
