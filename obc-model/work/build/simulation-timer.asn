Simulation-Timers-DataView DEFINITIONS ::=
BEGIN

   TimerData ::= SEQUENCE {
      timer-enabled BOOLEAN,
      interval INTEGER (0 .. 50000)
   }

   AggregateTimerData ::= SEQUENCE {
      
      
      
      
      
      state-handler-entrypoint SEQUENCE {
      },
      
      dummy-entry SEQUENCE {}
   }

END
