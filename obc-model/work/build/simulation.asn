Simulation-DataView DEFINITIONS ::=
BEGIN
   IMPORTS
      
      
      --  ASN.1 modules used by thread gui_send_tm_aoi
      Location-Fix-Packet FROM OBC-MODEL-DATAVIEW
      
      --  ASN.1 modules used by thread gui_send_tm_mcp
      Mode-Change-Packet FROM OBC-MODEL-DATAVIEW
      
      
      
      
      
      
      
      -- Import generic integer type (used for timers)
      T-UInt32 FROM TASTE-BasicTypes
      PID      FROM System-Dataview
      -- Import timers
      AggregateTimerData FROM Simulation-Timers-DataView
      --  Import the SDL function states needed for the global system state
      State-handler-entrypoint-Context FROM State-handler-entrypoint-Datamodel
   ;

   --  Simulator needs to knows about cyclic interfaces
   Periodic-Event {Event-Ty} ::= SEQUENCE {
      period INTEGER (0 .. 500000),  -- Upper limit is arbitrary
      event  Event-Ty
   }

   --  To keep a constant list of events.
   Periodic-Events {Event-Ty, INTEGER:max} ::=
      SEQUENCE (SIZE (0 .. max)) OF Periodic-Event {Event-Ty}

   
   
   
   Gui-Event ::= CHOICE {
      msg-in CHOICE {
         send-tm-aoi SEQUENCE { lfp Location-Fix-Packet},
         send-tm-mcp SEQUENCE { mcp Mode-Change-Packet}
      },
      msg-out CHOICE {
         trig-aoi SEQUENCE {   },
         trig-mcp SEQUENCE {   },
         trig-pwr SEQUENCE {   }
      }
   }
   
   
   
   Loc-Provider-Event ::= SEQUENCE {}  -- Synchronous function
   
   State-Handler-Entrypoint-Event ::= CHOICE {
      msg-in CHOICE {
         input-none SEQUENCE {},
         poll-aoi   SEQUENCE {  },
         poll-mcp   SEQUENCE {  },
         toggle-pwr SEQUENCE {  },
         trig-aoi   SEQUENCE {  },
         trig-mcp   SEQUENCE {  },
         trig-pwr   SEQUENCE {  }
      },
      msg-out CHOICE {
         send-tm-aoi SEQUENCE { lfp Location-Fix-Packet },
         send-tm-mcp SEQUENCE { mcp Mode-Change-Packet }
      }
   }
   State-Handler-Entrypoint-Periodic-Events ::=
      Periodic-Events {State-Handler-Entrypoint-Event, 3}
   
   state-handler-entrypoint-periodic-events State-Handler-Entrypoint-Periodic-Events ::= {
      { period 10000, event msg-in: poll-aoi : {} },
      { period 5000, event msg-in: poll-mcp : {} },
      { period 30000, event msg-in: toggle-pwr : {} }
   }
   
   Tc-Provider-Event ::= SEQUENCE {}  -- Synchronous function
   
   Tc-Validation-Event ::= SEQUENCE {}  -- Synchronous function
   
   Tm-Collection-Event ::= SEQUENCE {}  -- Synchronous function
   
   Tm-Provider-Event ::= SEQUENCE {}  -- Synchronous function
   

   --  Current observer state flag (used by model checkers)
   Observer-State-Kind ::= ENUMERATED {
      regular-state,
      error-state,
      ignore-state,
      success-state
   }

   --  Event related to the execution of a PI or call of a RI in the functional code
   Function-Event ::= CHOICE {
      gui                      Gui-Event,
      loc-provider             Loc-Provider-Event,
      state-handler-entrypoint State-Handler-Entrypoint-Event,
      tc-provider              Tc-Provider-Event,
      tc-validation            Tc-Validation-Event,
      tm-collection            Tm-Collection-Event,
      tm-provider              Tm-Provider-Event
   }

   --  Type used to store events in a database: associate a name to the event
   Named-Function-Event ::= SEQUENCE {
      id    IA5String (SIZE (1..80)),
      event Function-Event
   }

   --  Event at interface level (PI or RI), including source and destination ID
   Interface-Event ::= SEQUENCE {
      source PID,
      dest   PID,
      event  Function-Event
   }

   --  Event sent to the observers
   Observable-Event ::= CHOICE {
      no-event        SEQUENCE {},
      system-startup  SEQUENCE {},
      input-event     Interface-Event,   --  input event is evaluated after the transition
      output-event    Interface-Event,   --  output event is evaluated before the message is sent
      unhandled-input Interface-Event    --  message received in a state where it is not expected
   }

   --  constant that can be used to refer to the absence of an input/output event
   nothing Observable-Event ::= no-event : {}

   --  Define a queue of events, corresponding to the input queue for each function
   max-events INTEGER ::= 10
   Events-Ty ::= SEQUENCE (SIZE (0 .. max-events)) OF Observable-Event

   --  Global system state (excluding observers, which are defined later)
   state-handler-entrypoint-queue-size INTEGER ::= 2

   System-State ::= SEQUENCE {
      --  Timers
      timers AggregateTimerData,
      --  Message queues
      state-handler-entrypoint-queue Events-Ty (SIZE (0 .. state-handler-entrypoint-queue-size)),

      state-handler-entrypoint  State-handler-entrypoint-Context
   }

END
