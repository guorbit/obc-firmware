State-handler-entrypoint-Datamodel DEFINITIONS ::=
BEGIN
--  This file was generated automatically by OpenGEODE
IMPORTS
   CounterK, Time-UNIX, Latitude-WGS84, Longitude-WGS84, Location, Temperature-Generic, Deployment-Digital, Deployment-Analogue, System-Mode, Subsystem-Address, Mode-Change-Packet, Location-Fix-Packet FROM OBC-MODEL-DATAVIEW
   T-Int32, T-UInt32, T-Int8, T-UInt8, T-Boolean, T-Null-Record FROM TASTE-BasicTypes
   PID FROM System-Dataview;

State-handler-entrypoint-States ::= ENUMERATED {wait, sleep}

State-handler-entrypoint-Context ::= SEQUENCE {
   state State-handler-entrypoint-States,
   init-done BOOLEAN,
   k CounterK,
   s CounterK,
   w CounterK,
   k-max CounterK,
   s-max CounterK,
   w-max CounterK,
   mcp Mode-Change-Packet,
   lfp Location-Fix-Packet
}

END
