Context-tm-provider DEFINITIONS ::=
BEGIN
   IMPORTS
      CounterK FROM OBC-MODEL-DATAVIEW;

--  Group all context parameters of this function in a record
Context-tm-provider ::= SEQUENCE {
   k CounterK

}

--  Declare a constant with the values set by the user in the interface view
tm-provider-ctxt Context-tm-provider ::= {
   k 0

}
END
