Context-tc-provider DEFINITIONS ::=
BEGIN
   IMPORTS
      CounterK FROM OBC-MODEL-DATAVIEW;

--  Group all context parameters of this function in a record
Context-tc-provider ::= SEQUENCE {
   k CounterK

}

--  Declare a constant with the values set by the user in the interface view
tc-provider-ctxt Context-tc-provider ::= {
   k 0

}
END
